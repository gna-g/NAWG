module pdp-junos {

  namespace "https://internet2.edu/yang/pdp-junos";
  prefix pdp-junos;

  import tailf-common {
    prefix tailf;
  }
  import tailf-ncs {
    prefix ncs;
  }
  import junos {
    prefix junos;
  }
  import common {
    prefix i2c;
  }

  // internet2 common package
  import pdp {
    prefix pdp;
  }

  description
   "JunOS specific bits for PDP";

  // Augment PDP with some junos specific components.
  augment /ncs:services/pdp:pdp {
    uses junos;
  }

  // JunOS specific PDP config
  grouping junos {
    container junos {
      tailf:info "JunOS interfaces";

      when "starts-with(deref(../pdp:device)/../ncs:device-type/ncs:netconf/ncs:ned-id, 'juniper-junos-nc')" {
        tailf:dependency "../pdp:device";
      }
      must "not(count(interface/id) > 1 and count(../pdp:lag-id) = 0)" {
        error-message
         "lag-id must be set when more than one interface is specified";
        tailf:dependency "interface/id";
        tailf:dependency "../pdp:lag-id";
      }
      must "count(interface/id) >= 1" {
        error-message
         "At least one interface must be selected in a PDP";
        tailf:dependency "interface/id";
      }

      list interface {
        key "id";
        tailf:info "Interface ID";
        leaf id {
          type leafref {
            path "deref(../../../pdp:device)/../ncs:config/junos:configuration/junos:interfaces/junos:interface/junos:name";
          }
        }
        uses pdp:interface-fields;
      }
    }
  }
}
