module re {

  namespace "https://internet2.edu/yang/re";
  prefix re;

  import tailf-common {
    prefix tailf;
  }
  import tailf-ncs {
    prefix ncs;
  }
  import common {
    prefix i2c;
  }
  import peer-config {
    prefix peer-config;
  }
  import prefix-set {
    prefix prefix-set;
  }

  augment /ncs:services {
    uses re-participant-top;
    uses re-peer-top;
    uses re-ixp-top;
  }

  grouping re-participant-top {
    list re-participant {
      tailf:info "R&E Participant [Connector, Member, CAP/SEGP]";
      key name;
      tailf:cli-allow-wildcard;
      leaf name {
        type i2c:service-name;
        tailf:cli-allow-range;
      }

      uses ncs:service-data;
      ncs:servicepoint re-participant-servicepoint;

      uses re-private;
      uses re-intf-or-ixp;
      uses peer-config:multihop;
      // Require static route when multihop/ttl is set
      must "(not(multihop/ttl) or (multihop/static-route-ipv4) or (multihop/static-route-ipv6)) and ((multihop/ttl) or not(multihop/static-route-ipv4) or not(multihop/static-route-ipv6))" {
        error-message "When using eBGP multihop, both TTL and a static route must be defined";
      }
      must "(not(multihop/ttl) or (count(multihop/static-route-ipv4) < 2) and (count(multihop/static-route-ipv6) < 2))" {
        error-message "Must define only one static route for IPv4 and/or IPv6";
      }
      uses peer-config:admin-state;
      uses i2c:no-monitor-leaf;
      uses i2c:pending-leaf;
      uses i2c:unresponsive-leaf;
      uses i2c:service-id-leaf;
      uses i2c:entity-leaf;
      uses description-extra-leaf;

      uses peer-config:neighbor-config;
      must "count(neighbor)>0" {
        error-message "Must define at least one IPv4 or IPv6 neighbor";
      }

      container select-in {
        tailf:info "Specify routes that will be accepted, default accepts nothing";
        uses peer-config:match-DISABLE-PRIVATE-ASN-CHECK;
        uses match-PREFIX-WITH-TYPE;
      }
      // Note: no select-out-extra. participants get everything.

      uses peer-config:policy-exceptions;

      container vars {
        config false;
        tailf:cdb-oper {
          tailf:persistent true;
        }

        uses peer-config:vars-sdp;
        uses peer-config:vars-neighbor;
      }
      uses i2c:rejected-routes-action;
      uses i2c:route-report-action;
    }
  }

  grouping re-peer-top {
    list re-peer {
      tailf:info "R&E Peer [NET+, International, FedNet]";
      key name;
      tailf:cli-allow-wildcard;
      leaf name {
        type i2c:service-name;
        tailf:cli-allow-range;
      }

      uses ncs:service-data;
      ncs:servicepoint re-peer-servicepoint;

      uses re-private;
      uses re-intf-or-ixp;
      uses peer-config:admin-state;
      uses i2c:no-monitor-leaf;
      uses i2c:pending-leaf;
      uses i2c:unresponsive-leaf;
      uses i2c:service-id-leaf;
      uses i2c:entity-leaf;
      uses description-extra-leaf;
      uses peer-config:neighbor-config;
      must "count(neighbor)>0" {
        error-message "Must define at least one IPv4 or IPv6 neighbor";
      }

      leaf type {
        tailf:info "R&E Peer Type";
        mandatory true;
        type enumeration {
          enum international;
          enum fednet;
          enum netplus;
        }
      }


      container select-in {
        uses peer-config:match-PREFIX;
        uses peer-config:match-ANY;
      }

      container select-out-extra {
        tailf:info "EXPERT USE ONLY - Specify routes beyond the standard policy that will be advertised";
        uses peer-config:match-PREFIX;
        uses peer-config:match-ASPATH;
        uses peer-config:match-XRCOND;
      }
      uses peer-config:policy-exceptions;

      container vars {
        config false;
        tailf:cdb-oper {
          tailf:persistent true;
        }

        uses peer-config:vars-sdp;
        uses peer-config:vars-neighbor;
      }
      uses i2c:rejected-routes-action;
      uses i2c:route-report-action;
    }
  }

  grouping re-ixp-top {
    list re-ixp {
      tailf:info "R&E IXP - for multiple neighbors on a single sub-interface";
      key name;
      tailf:cli-allow-wildcard;
      leaf name {
        type i2c:service-name;
        tailf:cli-allow-range;
      }

      uses ncs:service-data;
      ncs:servicepoint re-ixp-servicepoint;
      uses peer-config:admin-state;
      uses i2c:entity-leaf;
      uses description-extra-leaf;

      uses peer-config:intf-config {
        refine override-mtu {
          tailf:info "Override the MTU [default 9000]";
        }
      }
      must "count(address-ipv4) > 0 or count(address-ipv6) > 0" {
        error-message "Must define at least one IPv4 or IPv6 address";
      }
      // this will eventually be integrated into intf-config
      uses peer-config:intf-config-ipv6-ra {
        refine ipv6-ra {
          tailf:info "IPv6 Router Advertisements [default suppress]";
          default suppress;
        }
      }

      container vars {
        config false;
        tailf:cdb-oper {
          tailf:persistent true;
        }

        uses peer-config:vars-sdp;
      }
    }
  }

  grouping description-extra-leaf {
    leaf description-extra {
      tailf:info "Extra information for bgp/sub-interface description, use as a last resort";
      type i2c:safe-string;
    }
  }

  grouping re-intf-or-ixp {

    uses peer-config:intf-config-OPTIONAL {
      refine override-mtu {
        tailf:info "Override the MTU [default 9000]";
      }
    }
    leaf re-ixp {
      type leafref {
        path "/ncs:services/re:re-ixp/re:name";
      }
    }

    container CONSTRAINTS {
      tailf:info "This is an empty container that's used because grouping/uses has syntax limitaitons";
      tailf:hidden "full";

      // Constraints - require PDP or the interface
      must "../re-ixp or ../pdp" {
        error-message "Must set either re-ixp or pdp";
      }
      must "not(../re-ixp and ../pdp)" {
        error-message "Cannot set both re-ixp and pdp";
      }

      // REMINDER: "if A, then B must be true" logic maps to "NOT(A) or B"

      // Require encap when PDP is used
      must "not(../pdp) or (../encapsulation/native or ../encapsulation/dot1q or ../encapsulation/qinq)" {
        error-message "When using a pdp, encapsulation must also be defined";
      }
      // Require address when PDP is used
      must "not(../pdp) or (count(../address-ipv4) + count(../address-ipv6) > 0)" {
        error-message "When using a pdp, at least one address-ipv4 or address-ipv6 must be set";
      }

      // Prevent encapsulation use when using an IXP
      must "not(../re-ixp) or not(../encapsulation/native or ../encapsulation/dot1q or ../encapsulation/qinq)" {
        error-message "When using an re-ixp, encapsulation must not be set on the re-participant/re-peer";
      }

      // Prevent encapsulation use when using an IXP
      must "not(../re-ixp) or (count(../address-ipv4) + count(../address-ipv6) = 0)" {
        error-message "When using an re-ixp, address-ipv4/address-ipv6 must not be set on the re-participant/re-peer";
      }

      // Prevent override-mtu use when using an IXP
      must "not(../override-mtu and ../re-ixp)" {
        error-message "Cannot use override-mtu and re-ixp at the same time";
      }
    }
  }

  grouping match-PREFIX-WITH-TYPE {
    list prefix {
      tailf:info "Match by named prefix-set";
      ordered-by user;
      key name;
      tailf:cli-allow-wildcard;
      leaf name {
        type leafref {
          path "/i2c:infrastructure/prefix-set:prefix-set/prefix-set:name";
        }
        tailf:cli-allow-range;
      }

      leaf type {
        mandatory true;
        type enumeration {
          enum participant {
            tailf:info "Tag as PARTICIPANT only";
          }
          enum segp {
            tailf:info "Tag as SEGP route, in addition to PARTICIPANT";
          }
          enum sponsored {
            tailf:info "Tag as SPONSORED route, in addition to PARTICIPANT";
          }
          enum corporate {
            tailf:info "Tag as CORPORATE route, in addition to PARTICIPANT";
          }
          enum rhcpp {
            tailf:info "Tag as RHCPP route, in addition to PARTICIPANT";
          }
        }
      }
    }
  }

  grouping re-private {
    container re-private {
      tailf:hidden "re-private";
      leaf re-deploy-counter {
        type uint32;
        tailf:info "Used internally to trigger a re-deploy when an re-ixp changes";
        default 0;
      }
    }
  }
}
