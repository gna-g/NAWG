module l3vpn {

  namespace "https://internet2.edu/yang/l3vpn";
  prefix l3vpn;

  import tailf-common {
    prefix tailf;
  }
  import tailf-ncs {
    prefix ncs;
  }
  import common {
    prefix i2c;
  }
  import peer-config {
    prefix peer-config;
  }
  import prefix-set {
    prefix prefix-set;
  }
  import ietf-inet-types {
    prefix inet;
  }

  augment /ncs:services {
    uses xsede-participant-top;
    uses lhcone-ixp-top;
    uses lhcone-peer-top;
    uses lhcone-participant-top;
    uses scrubbed-subscriber-top;
    uses scrubbed-provider-top;
  }

  grouping xsede-participant-top {
    list xsede-participant {
      tailf:info "XSEDE Participant";
      tailf:cli-allow-wildcard;

      key name;
      leaf name {
        type i2c:service-name;
        tailf:cli-allow-range;
      }

      uses ncs:service-data;
      ncs:servicepoint xsede-participant-servicepoint;

      uses l3vpn-vars;

      uses peer-config:admin-state;
      uses i2c:service-id-leaf;
      uses i2c:entity-leaf;
      uses i2c:no-monitor-leaf;
      uses i2c:pending-leaf;
      uses i2c:unresponsive-leaf;
      uses description-extra-leaf;
      uses peer-config:neighbor-config;

      uses peer-config:intf-config {
        refine override-mtu {
          tailf:info "Override the MTU [default 9000]";
        }
      }

      uses i2c:rejected-routes-action;
    }
  }

  grouping lhcone-private {
    container lhcone-private {
      tailf:hidden "lhcone-private";
      leaf re-deploy-counter {
        type uint32;
        tailf:info "Used internally to trigger a re-deploy when an lhcone-ixp changes";
        default 0;
      }
    }
  }

  grouping lhcone-ixp-top {
    list lhcone-ixp {
      tailf:info "lhcone-ixp - multi-tenant peering";
      tailf:cli-allow-wildcard;

      key name;
      leaf name {
        type i2c:service-name;
        tailf:cli-allow-range;
      }

      uses ncs:service-data;
      ncs:servicepoint lhcone-ixp-servicepoint;

      uses peer-config:admin-state;

      uses i2c:entity-leaf;
      uses description-extra-leaf {
        refine description-extra {
          tailf:info "Extra information for sub-interface, does not affect services on-top of IXP";
        }
      }

      uses peer-config:intf-config {
        refine override-mtu {
          tailf:info "Override the MTU [default 9000d]";
        }
      }

      must "count(address-ipv4) > 0 or count(address-ipv6) > 0" {
        error-message "Must define at least one IPv4 or IPv6 address";
      }

      uses l3vpn-vars;
    }
  }

  grouping lhcone-intf-or-ixp {
    uses peer-config:intf-config-OPTIONAL {
      refine override-mtu {
        tailf:info "Override the MTU [default 9000]";
      }
    }

    leaf lhcone-ixp {
      tailf:info "Set up peer on an IXP";
      type leafref {
        path "/ncs:services/l3vpn:lhcone-ixp/l3vpn:name";
      }
    }

    container CONSTRAINTS {
      tailf:info "This is an empty container that's used because grouping/uses has syntax limitaitons";
      tailf:hidden "full";

      // Constraints - require PDP or the interface
      must "../lhcone-ixp or ../pdp" {
        error-message "Must set either lhcone-ixp or pdp";
      }
      must "not(../lhcone-ixp and ../pdp)" {
        error-message "Cannot set both lhcone-ixp and pdp";
      }

      // REMINDER: "if A, then B must be true" logic maps to "NOT(A) or B"

      // Require encap when PDP is used
      must "not(../pdp) or (../encapsulation/native or ../encapsulation/dot1q or ../encapsulation/qinq)" {
        error-message "When using a pdp, encapsulation must also be defined";
      }
      // Require address when PDP is used
      must "not(../pdp) or (count(../address-ipv4) + count(../address-ipv6) > 0)" {
        error-message "When using a pdp, at least one address-ipv4 or address-ipv6 must be set";
      }

      // Prevent encapsulation use when using an IXP
      must "not(../lhcone-ixp) or not(../encapsulation/native or ../encapsulation/dot1q or ../encapsulation/qinq)" {
        error-message "When using an lhcone-ixp, encapsulation must not be set on the lhcone-cust/lhcone-peer";
      }

      // Prevent encapsulation use when using an IXP
      must "not(../lhcone-ixp) or (count(../address-ipv4) + count(../address-ipv6) = 0)" {
        error-message "When using an lhcone-ixp, address-ipv4/address-ipv6 must not be set on the lhcone-cust/lhcone-peer";
      }

      // Prevent override-mtu use when using an IXP
      must "not(../override-mtu and ../lhcone-ixp)" {
        error-message "Cannot use override-mtu and lhcone-ixp at the same time";
      }
    }
  }

  grouping lhcone-peer-top {
    list lhcone-peer {
      tailf:info "LHCONE Peer";
      tailf:cli-allow-wildcard;

      key name;
      leaf name {
        type i2c:service-name;
        tailf:cli-allow-range;
      }

      uses ncs:service-data;
      ncs:servicepoint lhcone-peer-servicepoint;

      uses l3vpn-vars;


      uses peer-config:admin-state;
      uses i2c:service-id-leaf;
      uses i2c:entity-leaf;
      uses i2c:no-monitor-leaf;
      uses i2c:pending-leaf;
      uses i2c:unresponsive-leaf;
      uses description-extra-leaf;
      uses peer-config:neighbor-config;
      uses lhcone-private;

      uses lhcone-intf-or-ixp;

      uses peer-config:policy-exceptions;

      uses i2c:rejected-routes-action;
    }
  }

  grouping lhcone-participant-top {
    list lhcone-participant {
      tailf:info "LHCONE Participant";
      tailf:cli-allow-wildcard;

      key name;
      leaf name {
        type i2c:service-name;
        tailf:cli-allow-range;
      }

      uses ncs:service-data;
      ncs:servicepoint lhcone-participant-servicepoint;

      uses l3vpn-vars;


      uses peer-config:admin-state;
      uses i2c:service-id-leaf;
      uses i2c:entity-leaf;
      uses i2c:no-monitor-leaf;
      uses i2c:pending-leaf;
      uses i2c:unresponsive-leaf;
      uses description-extra-leaf;
      uses peer-config:neighbor-config;
      uses lhcone-private;

      uses lhcone-intf-or-ixp;

      container select-in {
        tailf:info "Specify routes that will be accepted, default accepts nothing";
        uses peer-config:match-PREFIX;
      }

      uses peer-config:policy-exceptions;

      uses i2c:rejected-routes-action;
    }
  }

  grouping scrubbed-subscriber-top {
    list scrubbed-subscriber {
      tailf:info "Scrubbed Subscriber";
      tailf:cli-allow-wildcard;

      key name;
      leaf name {
        type i2c:service-name;
        tailf:cli-allow-range;
      }

      uses ncs:service-data;
      ncs:servicepoint scrubbed-subscriber-servicepoint;

      uses l3vpn-vars;


      uses peer-config:admin-state;
      uses i2c:service-id-leaf;
      uses i2c:entity-leaf;
      uses i2c:no-monitor-leaf;
      uses i2c:pending-leaf;
      uses i2c:unresponsive-leaf;
      uses description-extra-leaf;
      uses peer-config:neighbor-config;

      uses peer-config:intf-config {
        refine override-mtu {
          tailf:info "Override the MTU [default 9000]";
        }
      }

      uses i2c:rejected-routes-action;
    }
  }

  grouping scrubbed-provider-top {
    list scrubbed-provider {
      tailf:info "Scrubbed Provider";
      tailf:cli-allow-wildcard;

      key name;
      leaf name {
        type i2c:service-name;
        tailf:cli-allow-range;
      }

      uses ncs:service-data;
      ncs:servicepoint scrubbed-provider-servicepoint;

      uses l3vpn-vars;

      uses peer-config:admin-state;
      uses i2c:service-id-leaf;
      uses i2c:entity-leaf;
      uses i2c:no-monitor-leaf;
      uses i2c:pending-leaf;
      uses i2c:unresponsive-leaf;
      uses description-extra-leaf;
      uses peer-config:neighbor-config;

      uses peer-config:intf-config {
        refine override-mtu {
          tailf:info "Override the MTU [default 9000]";
        }
      }

      uses i2c:rejected-routes-action;
    }
  }

  grouping l3vpn-vars {

    container vars {
      config false;
      tailf:cdb-oper {
        tailf:persistent true;
      }

      leaf vrf-name {
        tailf:info "VRF Name";
        type string;
      }
      leaf vrf-asn {
        tailf:info "VRF ASN";
        type uint32;
      }

      container bgp {
        leaf id {
          tailf:info "BGP ID";
          type uint16;
        }
      }

      uses peer-config:vars-sdp;
      uses peer-config:vars-neighbor;
    }
  }


  grouping description-extra-leaf {
    leaf description-extra {
      tailf:info "Extra information for bgp/sub-interface description, use as a last resort";
      type i2c:safe-string;
    }
  }

}
