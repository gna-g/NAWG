module simplepw {

  namespace "http://internet2.edu/yang/simplepw";
  prefix simplepw;

  import ietf-inet-types {
    prefix inet;
  }
  import tailf-common {
    prefix tailf;
  }
  import tailf-ncs {
    prefix ncs;
  }
 import pdp {
    prefix i2-pdp;
  }
  import common {
    prefix i2c;
  }
  description
    "Service for a simple ptp martini pw mainly for SMN";

  augment /ncs:services {
    uses simplepw-list;
  }

  grouping simplepw-list {
    list simplepw {

      key name;
      leaf name {
        tailf:info "Service name (e.g SMN-PHOE-TULS-1)";
        tailf:cli-allow-range;
        type i2c:service-name;
      }

      uses ncs:service-data;
      ncs:servicepoint simplepw-servicepoint;

      list pdp {
        tailf:info "Internet2 Physical Delivery Point - backbone service must define exactly 2 PDPs.";
        key name;

        leaf name {
          type leafref {
            path "/ncs:services/i2-pdp:pdp/i2-pdp:name";
          }
        }
        min-elements 2;
        max-elements 2;

        choice encapsulation {
          mandatory true;
          leaf vlan {
            tailf:info "Specify VLAN ID";
            type uint16 {
              range "2..4078";
            }
          }
          leaf native {
            tailf:info "Pass all traffic";
            type empty;
          }
        }
      }

      leaf type {
        tailf:info "Service type, out of list; if you're choosing Other, please let Architecture know";
        mandatory true;
        type enumeration {
          enum SMN;
          enum Other;
        }
      }

      leaf admin-state {
        tailf:info "Admin-state for simplepw";
        type enumeration {
          enum no-config {
            tailf:info "Input parameters into NSO but do not apply configuration to a device";
          }
          enum in-service {
            tailf:info "Service is in active-use";
          }
        }
        mandatory true;
      }

      leaf circuit-id {
        tailf:info "CircuitID for end-to-end service";
        type uint32;
      }

      container vars {
        config false;
        tailf:info "Processed config from Python";
        tailf:cdb-oper {
          tailf:persistent true;
        }
        leaf description-auto {
          tailf:info "Sub-interface description";
          type string;
        }

        list endpoint {
          tailf:info "Simple PW endpoint";
          key pdp;
          leaf pdp {
            tailf:info "Referenced PDP";
            type leafref {
              path "/ncs:services/i2-pdp:pdp/i2-pdp:name";
            }
          }
          leaf if-full {
            tailf:info "PDP interface name";
            type string;
          }
          leaf neighbor-ip {
            tailf:info "PW neighbor IP";
            type inet:ip-address;
          }
        }
        leaf pw-id {
          tailf:info "PW ID - autogenerated by the service python";
          type uint32 {
            range "40000..49999";
          }
        }
      }
    }
  }
}
