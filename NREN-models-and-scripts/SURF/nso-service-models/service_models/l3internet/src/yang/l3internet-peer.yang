submodule l3internet-peer {
    belongs-to l3internet {
        prefix l3internet;
    }

    import ietf-inet-types {
        prefix inet;
    }
    import tailf-ncs {
        prefix ncs;
    }
    import tailf-common {
        prefix tailf;
    }
    import surfnet-common {
        prefix surfnet;
    }
    import ptp {
        prefix ptp;
    }

    include l3internet-bgp;
    include l3internet-endpoint;

    revision 2016-01-01 {
        description
          "Initial revision.";
    }
    augment /ncs:services {
        list l3internet-peer {
            description
              "This service is used to configure external IP peerings";

            uses ncs:service-data;
            ncs:servicepoint "l3internet-peer";

            key name;
            leaf name {
                tailf:info "Unique service id (UUID) (nso-id)";
                type string;
            }

            uses surfnet:workflow_service;

            leaf peer_name {
                tailf:info "Name of peer (no spaces)";
                mandatory true;
                type string {
                    pattern
                      '[a-zA-Z0-9\-_]+';
                }
            }

            leaf peer_as {
                mandatory true;
                tailf:info "Peer AS number";
                type inet:as-number;
            }

            leaf multipath {
                tailf:info "Use multipath";
                type boolean;
            }

            leaf ipv4_max_prefix {
                tailf:info "Max prefix for IPv4";
                type uint32;
            }

            leaf ipv6_max_prefix {
                tailf:info "Max prefix for IPv6";
                type uint32;
            }

            leaf blackhole_community {
                tailf:info "Blackhole community for peer";
                type string {
                    pattern
                      '([0-9]+:[0-9]+)';
                }
            }

            list community_list_out {
                tailf:info "List of BGP communities to add with announcements";
                key "community";

                leaf "community" {
                    tailf:info "Extra community to add";
                    type string {
                        pattern
                          '([0-9]+:[0-9]+)';
                    }
                }
            }

            leaf peer_community {
                tailf:info "Second part of SURFnet import-policy community for peer(-group) (1103:x) (for IX & Transit) - normally inherit from group";

                type inet:as-number;
            }

            leaf as_prepend {
                tailf:info "Number of outgoing SURFnet AS-prepends";
                type uint32 {
                    range "1..5";
                }
            }

            list peerings {
                key "name";
                leaf name {
                    tailf:info "Unique service id <UUID> (instance-id)";
                    type string;
                }

                leaf peer_group {
                    tailf:info "BGP peer-group name";
                    mandatory true;
                    type leafref {
                        path "/ncs:services/l3internet:l3internet-peer-group/l3internet:name";
                    }
                }

                leaf ipv4_remote_address {
                    tailf:info "Remote IP Address (x.x.x.x)";
                    type inet:ipv4-address;
                }

                leaf ipv6_remote_address {
                    tailf:info "Remote IPv6 Address (2001:610:fc7::145:145:x:x)";
                    type inet:ipv6-address;
                }

                leaf metric_out {
                    tailf:info "BGP metric-out for peer";
                    type uint32;
                }

                leaf session_priority {
                    tailf:info "Uses BGP local-pref to prefer peering (only use if needed)";
                    type enumeration {
                        enum primary;
                        enum secondary;
                        enum tertiary;
                        enum quaternary;
                    }
                }
                
                leaf as_prepend {
                    tailf:info "Number of outgoing SURFnet AS-prepends";
                    type uint32 {
                        range "1..5";
                    }
                }                

                leaf export_reject_all {
                    tailf:info "Set BGP export policy to reject-all";
                    type boolean;
                    default false;
                }

                leaf import_reject_all {
                    tailf:info "Set BGP import policy to reject-all";
                    type boolean;
                    default false;
                }

                uses bgp-settings;

                leaf port {
                    type leafref {
                        path "/ncs:services/l3internet:l3internet-peering-port/l3internet:name";
                    }
                }
            }
        }
    }
}
