module esnet-boilerplate {
  namespace "http://es.net/esnet-boilerplate";
  prefix esnet-boilerplate;

  import tailf-ncs {
    prefix tailf-ncs;
  }

  organization "ESnet";
  contact "ESnet www.es.net";
  description "ESnet Boilerplate Service";

  augment /tailf-ncs:services {
    description "Boilerplate Configuration";
    list boilerplate {
      key device;
      uses tailf-ncs:service-data;
      tailf-ncs:servicepoint "esnet-boilerplate";
      description "ESnet boilerplate base configuration instances";
      leaf device {
        type leafref {
          path "/tailf-ncs:devices/tailf-ncs:device/tailf-ncs:name";
        }
        description "Device to use";
      }

      leaf orch-id {
        type string;
        description "Orchestrator id";
      }
    }
  }
}
