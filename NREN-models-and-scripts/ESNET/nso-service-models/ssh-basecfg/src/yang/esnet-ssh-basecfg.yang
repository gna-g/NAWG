module esnet-ssh-basecfg {
  namespace "http://es.net/esnet-ssh-basecfg";
  prefix esnet-ssh-basecfg;

  import tailf-ncs {
    prefix tailf-ncs;
  }

  organization "ESnet";
  contact "ESnet www.es.net";
  description "ESnet SSH Service";


  augment /tailf-ncs:services {
    description "Service Configuration";
    list ssh-basecfg {
      key device;
      uses tailf-ncs:service-data;
      tailf-ncs:servicepoint "esnet-ssh-basecfg";
      description "SSH service";

      leaf device {
        type leafref {
          path "/tailf-ncs:devices/tailf-ncs:device/tailf-ncs:name";
        }
        description "Device to use";
      }

      leaf orch-id {
        type string;
        description "Orchestrator id";
      }
    }
  }
}
