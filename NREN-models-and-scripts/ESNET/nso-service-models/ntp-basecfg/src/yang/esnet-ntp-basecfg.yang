module esnet-ntp-basecfg {

  namespace "http://es.net/esnet-ntp-basecfg";
  prefix esnet-ntp-basecfg;

  import ietf-inet-types {
    prefix ietf-inet-types;
  }
  import tailf-ncs {
    prefix tailf-ncs;
  }

  organization "ESnet";
  contact "ESnet www.es.net";
  description "ESnet NTP Base Configuration";

  grouping server_params {
    description "NTP server parameters";
    leaf name {
      type string {
        length "1..30";
        pattern "[a-zA-Z0-9_.-]+";
      }
      description "NTP server name";
    }
    choice address {
      mandatory true;
      description "server address";

      case ipv6 {
        leaf ipv6-address {
          type ietf-inet-types:ipv6-address;
          description "NTP server IPv6 address";
        }
      }
      case ipv4 {
        leaf ipv4-address {
          type ietf-inet-types:ipv4-address;
          description "NTP server IPv4 address";
        }
      }
    }
  }

  augment /tailf-ncs:services {
    description "Service Configuration";
    list ntp-basecfg {
      key device;
      uses tailf-ncs:service-data;
      tailf-ncs:servicepoint "esnet-ntp-basecfg";

      description "ESnet NTP Base Configuration";

      leaf orch-id {
        type string;
        description "Orchestrator id";
      }
      leaf device {
        type leafref {
          path "/tailf-ncs:devices/tailf-ncs:device/tailf-ncs:name";
        }
        description "Device to use";
      }
      list ntp-server {
        key name;
        min-elements 1;
        description "NTP server information";
        uses server_params;
      }
    }
  }
}
